# -*- coding: utf-8 -*-

import FreeCAD as App
import FreeCADGui as Gui
import PartDesign
import PartDesignGui
import Sketcher
import Draft

#import os
#os.system('cls')

# Parameters
int_diametrocirculo = 2
int_ladoSimetrico = 7
int_cifra_desconocida_1 = 2
int_cifra_desconocida_2 = 6
int_cifra_desconocida_3 = 3  # seems to be a radius

def create_new_document(name):
    doc = App.getDocument(name)
    doc.recompute()
    return doc

def create_body(doc, body_name):
    body = doc.addObject('PartDesign::Body', body_name)
    doc.recompute()
    return body

def create_sketch_on_xy_plane(doc, body):
    sketch = body.newObject('Sketcher::SketchObject', 'Sketch')
    sketch.Support = (doc.getObject('XY_Plane'), [''])
    sketch.MapMode = 'FlatFace'
    doc.recompute()
    return sketch

def add_circle_to_sketch(sketch):
    sketch.addGeometry(Part.Circle(App.Vector(0, 0, 0), App.Vector(0, 0, 1), int_diametrocirculo), False)
    sketch.addConstraint(Sketcher.Constraint('Coincident', 0, 3, -1, 1)) 
    sketch.recompute()

def create_sketch_on_xz_plane(doc, body):
    sketch = body.newObject('Sketcher::SketchObject', 'Sketch001')
    sketch.Support = (doc.getObject('XZ_Plane'), [''])
    sketch.MapMode = 'FlatFace'
    doc.recompute()
    return sketch

def add_lines_and_fillet_to_sketch(sketch):
    sketch.addGeometry(Part.LineSegment(App.Vector(0, 0, 0), App.Vector(0, int_ladoSimetrico, 0)), False)
    sketch.addConstraint(Sketcher.Constraint('Coincident', -1, 1, 0, 1)) 
    sketch.addConstraint(Sketcher.Constraint('PointOnObject', 0, 2, -2)) 
    sketch.addGeometry(Part.LineSegment(App.Vector(0, int_ladoSimetrico, 0), App.Vector(int_ladoSimetrico, int_ladoSimetrico, 0)), False)
    sketch.addConstraint(Sketcher.Constraint('Coincident', 0, 2, 1, 1)) 
    sketch.addConstraint(Sketcher.Constraint('Horizontal', 1)) 
    sketch.fillet(1, 0, App.Vector(int_cifra_desconocida_1, int_ladoSimetrico, 0), App.Vector(0, int_cifra_desconocida_2, 0), int_cifra_desconocida_3, True, False)
    sketch.recompute()

def create_additive_pipe(doc, body):
    pipe = body.newObject('PartDesign::AdditivePipe', 'AdditivePipe')
    pipe.Profile = body.getObject('Sketch')
    #doc.recompute()
    body.getObject('Sketch').Visibility = False
    #doc.recompute()
    pipe.Spine = (body.getObject('Sketch001'), [])
    doc.recompute()

def set_view_to_axonometric():
    view = Gui.ActiveDocument.ActiveView
    view.viewAxonometric()
    view.fitAll()

#def move_body_along_axes(body, distanceX, distanceY, distanceZ):
def create_placement(body):
    placement = body.Placement
    placement.Base.x = 0
    placement.Base.y = 0
    placement.Base.z = 0
    body.Placement = placement
    #print("recompute create_placement")
    App.ActiveDocument.recompute()

#def copy_and_paste_body(doc, body, dx, dy, dz, new_body_name):
def copy_and_paste_body9(doc, body, new_body_name):

    if(False):    
        copied_body = Draft.clone(body)
        copied_body.Label = new_body_name
        
    if(True):
        Gui.Selection.addSelection(doc.Name, body)    
        body = doc.getObject("Body1")
        Gui.runCommand('Std_Copy', 0)
        Gui.Selection.clearSelection()
        Gui.runCommand('Std_Paste', 0)
        new_body = doc.getObject(body_name + '_Copy')
        new_body.Label = new_body_name

    return new_body

#def create_and_set_objects(doc_name, lst_names_Body_i, lst_names_Features_i):
def create_and_set_objects(doc_name, lst_names_Body_i, lst_names_Features_i, str_clon_original):
    doc = App.getDocument(doc_name)
    
    if not doc:
        print(f"Document '{doc_name}' not found.")
        return

    # Add new Body and Feature objects
    body = doc.addObject('PartDesign::Body', lst_names_Body_i)
    feature = doc.addObject('PartDesign::FeatureBase', lst_names_Features_i)
    
    # Group the feature under the body
    body.Group = [feature]
    
    # Set the Tip of the body to the feature
    body.Tip = feature
    
    if True:
        # Check if the original clone exists
        original_clone = None
        for obj in doc.Objects:
            if obj.Name == str_clon_original:
                original_clone = obj
                break
    
        if original_clone:
            # If the original clone exists, use its placement as a base for the new feature
            feature.BaseFeature = original_clone
        
            # Create a copy of the placement from the original clone to avoid direct dependency
            feature.Placement = original_clone.Placement.copy()
        else:
            # If the original clone does not exist, set a default placement
            print(f"Object '{str_clon_original}' not found. Setting default placement.")
            feature.Placement = App.Placement()  # Set to default placement if original_clone is not found

    #feature.Placement = App.Placement()    

    # Detach editor mode from original reference
    feature.setEditorMode('Placement', 0)

    # Recompute the document to apply changes
    doc.recompute()


def main():
    doc = create_new_document("HollowCylindersTShape")
    
    #lst_names=["Body1", "Body2", "Body3", "Body4", "Body5", "Body6"]
    
    #for i in list(range(6)):
    #for lst_names_i in lst_names:
    
    str_clon_original="BodyOriginal"
    if (True):
        initial_body = create_body(doc, str_clon_original)
        sketch1 = create_sketch_on_xy_plane(doc, initial_body)
        add_circle_to_sketch(sketch1)
        sketch2 = create_sketch_on_xz_plane(doc, initial_body)
        add_lines_and_fillet_to_sketch(sketch2)
        create_additive_pipe(doc, initial_body)
    
    #positions = [
    #    (10, 0, -40),
    #    (20, 0, -40),
    #    (30, 0, -40),
    #    (-10, 0, -40),
    #    (-20, 0, -40),
    #    (-30, 0, -40)
    #]
    
    lst_names_Body=["Body1", "Body2", "Body3", "Body4", "Body5", "Body6"]
    lst_names_Features=["Clone1", "Clone2", "Clone3", "Clone4", "Clone5", "Clone6"]
    #lst_names=["Body11"]
#    for i in list(range(6)):
    for lst_names_Body_i, lst_names_Features_i  in zip(lst_names_Body, lst_names_Features):

        if(False):
            App.getDocument('HollowCylindersTShape').addObject('PartDesign::Body',lst_names_Body_i)
            App.getDocument('HollowCylindersTShape').addObject('PartDesign::FeatureBase',lst_names_Features_i)

            App.getDocument('HollowCylindersTShape').getObject(lst_names_Body_i).Group = [App.getDocument('HollowCylindersTShape').getObject(lst_names_Features_i)]
            App.getDocument('HollowCylindersTShape').getObject(lst_names_Body_i).Tip = App.getDocument('HollowCylindersTShape').getObject(lst_names_Features_i)
            App.getDocument('HollowCylindersTShape').getObject(lst_names_Features_i).BaseFeature = App.getDocument('HollowCylindersTShape').getObject(str_clon_original)
            App.getDocument('HollowCylindersTShape').getObject(lst_names_Features_i).Placement = App.getDocument('HollowCylindersTShape').getObject(str_clon_original).Placement
            App.getDocument('HollowCylindersTShape').getObject(lst_names_Features_i).setEditorMode('Placement', 0)
        
        #doc = App.getDocument('HollowCylindersTShape')
        #body = doc.addObject('PartDesign::Body', lst_names_Body_i)
        #feature = doc.addObject('PartDesign::FeatureBase', lst_names_Features_i)
        #body.Group = [feature]
        #body.Tip = feature
        create_and_set_objects('HollowCylindersTShape', 
                               lst_names_Body_i, 
                               lst_names_Features_i,
                               str_clon_original)

#App.ActiveDocument.recompute()
 
        #copy_and_paste_body(doc, initial_body, *pos, f"Body{i+2}")
        #copy_and_paste_body(doc, initial_body, f"Body{i+2}")
        #initial_body.copy()
        #doc.addObject('PartDesign::Body', lst_names_i)
        #delete_body(doc, "Body1")
        #initial_body = create_body(doc, lst_names_i)
        #sketch1 = create_sketch_on_xy_plane(doc, initial_body)
        #add_circle_to_sketch(sketch1)
        #sketch2 = create_sketch_on_xz_plane(doc, initial_body)
        #add_lines_and_fillet_to_sketch(sketch2)
        #create_additive_pipe(doc, initial_body)
    
    if(False):
        App.getDocument('HollowCylindersTShape').removeObject(str_clon_original)
        App.getDocument('HollowCylindersTShape').removeObject('AdditivePipe')
        App.getDocument('HollowCylindersTShape').removeObject('Sketch')
        App.getDocument('HollowCylindersTShape').removeObject('Sketch001')


        App.getDocument('HollowCylindersTShape').recompute()

    if(False):
        body = doc.getObject("Body11")

        # Modify the placement
        new_placement = body.Placement
        new_placement.Base.x = 10  # Move 10 units along the X-axis
        new_placement.Base.y = 0   # Move 0 units along the Y-axis
        new_placement.Base.z = 0   # Move 0 units along the Z-axis

        # Apply the new placement
        body.Placement = new_placement


    obj = doc.getObject(str_clon_original)
    obj.Visibility = not obj.Visibility
    Gui.updateGui()

    set_view_to_axonometric()

if __name__ == "__main__":
    main()
