import FreeCAD as App

# Ensure the document is loaded and active
doc = App.getDocument('HollowCylindersTShape')


def func_newPlacement(x,y,z,nombre):
    # Get the body you want to modify
    body = doc.getObject(nombre)

    # Modify the placement
    new_placement = body.Placement
    new_placement.Base.x = x  # Move 10 units along the X-axis
    new_placement.Base.y = y   # Move 0 units along the Y-axis
    new_placement.Base.z = z   # Move 0 units along the Z-axis

    # Apply the new placement
    body.Placement = new_placement


def rotate_object(obj_name, angle, axis):
  
    obj = doc.getObject(obj_name)
    
    # Create a rotation object
    rotation = App.Rotation(App.Vector(axis[0], axis[1], axis[2]), angle)
    
    # Apply rotation to the object's current placement
    obj.Placement.Rotation = rotation.multiply(obj.Placement.Rotation)
    
    # Recompute document to apply changes
    doc.recompute()



############
############
############
func_newPlacement(10,0,0,"TShape1")
func_newPlacement(-10,0,0,"TShape2")
############
func_newPlacement(10,0,-10,"Cilindrito1")
func_newPlacement(-10,0,-10,"Cilindrito2")
func_newPlacement(10,0,-20,"Cilindrito3")
func_newPlacement(-10,0,-20,"Cilindrito4")
############

############
func_newPlacement(30,0,-50,"CilindroGrande1")
func_newPlacement(35,0,-50,"CilindroGrande2")
func_newPlacement(40,0,-50,"CilindroGrande3")
func_newPlacement(45,0,-50,"CilindroGrande4")
############
func_newPlacement(10,0,-30,"Body1")
func_newPlacement(-10,0,-30,"Body2")
func_newPlacement(10,0,-40,"Body3")
func_newPlacement(-10,0,-40,"Body4")
func_newPlacement(10,0,-50,"Body5")
func_newPlacement(-10,0,-50,"Body6")




############
############
############
############
    
boo_rotate=False
#boo_rotate=True
if(boo_rotate):
    rotate_object('TShape1', -90, (0, 1, 0)) 
    rotate_object('Cilindrito1', -90, (0, 1, 0)) 
    rotate_object('Body1', 90, (0, 1, 0)) 
    rotate_object('Body2', -90, (0, 1, 0)) 
    rotate_object('Cilindrito2', -90, (0, 1, 0)) 
    rotate_object('Body3', 90, (0, 1, 0)) 
    rotate_object('Body3', 180, (1, 0, 0)) 
    rotate_object('CilindritoAserruchado1', -90, (0, 1, 0)) 
    #rotate_object('CilindritoAserruchado2', -90, (0, 1, 0)) 

func_newPlacement(0,0,0,"TShape1")
func_newPlacement(20,0,0,"Cilindrito1")
func_newPlacement(25,0,0,"Body1")
func_newPlacement(32,0,-70,"CilindroGrande1")
func_newPlacement(39,0,-80,"Body2")
func_newPlacement(50,0,-80,"Cilindrito2")
func_newPlacement(53,0,-80,"Body3")
func_newPlacement(60,0,-70,"CilindroGrande2")

func_newPlacement(10,0,0,"CilindritoAserruchado1")
#func_newPlacement(60,0,-80,"CilindritoAserruchado2")
############
############
############
############
    
if(boo_rotate):
    rotate_object('TShape2', -90, (0, 1, 0)) 
    rotate_object('Cilindrito3', -90, (0, 1, 0)) 
    rotate_object('Body4', 90, (0, 1, 0)) 
    rotate_object('Body5', -90, (0, 1, 0)) 
    rotate_object('Cilindrito4', -90, (0, 1, 0)) 
    rotate_object('Body6', 90, (0, 1, 0)) 
    rotate_object('Body6', 180, (1, 0, 0)) 
    rotate_object('CilindritoAserruchado3', -90, (0, 1, 0)) 
    #rotate_object('CilindritoAserruchado4', -90, (0, 1, 0)) 

func_newPlacement(0,100,0,"TShape2")
func_newPlacement(20,100,0,"Cilindrito3")
func_newPlacement(25,100,0,"Body4")
func_newPlacement(32,100,-70,"CilindroGrande3")
func_newPlacement(39,100,-80,"Body5")
func_newPlacement(50,100,-80,"Cilindrito4")
func_newPlacement(53,100,-80,"Body6")
func_newPlacement(60,100,-70,"CilindroGrande4")

func_newPlacement(10,100,0,"CilindritoAserruchado3")
#func_newPlacement(60,100,-80,"CilindritoAserruchado4")



###############
#COLORES
###############

if(False):
    view_object = Gui.getDocument("HollowCylindersTShape").getObject("TShape2")
    view_object.DiffuseColor = [(1.,0.,0.)]
    Gui.Selection.addSelection('HollowCylindersTShape','Cilindrito3','Face2',0.,0.,1.)

#view_object = App.getDocument("HollowCylindersTShape").getObject("TShape2")
#Gui.ActiveDocument.Box.DiffuseColor=[(1.,0.,0.),(0.,1.,0.),(0.,0.,1.),(1.,1.,0.),(1.,0.,1.),(0.,1.,1.)]
#view_object.DiffuseColor = (1.0,1.0,0.0)#TIene que tener decimales o sino queda negro




    
# Recompute the document to apply changes



def func_changeColors(nombreShape, face_index, bocaGrandeoPequeña):
    import FreeCAD as App
    import FreeCADGui as Gui

    # Select the specific face of the object
    #Gui.Selection.clearSelection()  # Clear any previous selections
    #Gui.Selection.addSelection('HollowCylindersTShape', nombreShape, nombreFace)

    # Get the selected object and its view object
    doc = App.getDocument('HollowCylindersTShape')
    obj = doc.getObject(nombreShape)
    view_obj = Gui.getDocument('HollowCylindersTShape').getObject(nombreShape)

    # Set the color for the specific face (assuming face index 2 for 'Face3')
    # The DiffuseColor property is a list where each index corresponds to a face
    #face_index = 2  # Adjust this index based on your face numbering


    # Ensure the DiffuseColor list is long enough
    #colors = list(view_obj.DiffuseColor) if hasattr(view_obj, 'DiffuseColor') else []
    #print("colors: ", colors)
    #while len(colors) <= face_index:
    #    colors.append((1.0, 1.0, 1.0))  # Default to white if there are not enough colors
    #for i in colors:
    #colors.append((204.0, 204.0, 204.0))

    if(bocaGrandeoPequeña=="bocaPequeña"):
        color = (0.0, 1.0, 0.0)  # Green color
    elif(bocaGrandeoPequeña=="bocaGrande"):
        color = (1.0, 0.0, 0.0)  # Red color    
    else:
        0/0 #ingresar string correcto

    coloresAnteriores = view_obj.DiffuseColor
    #print("coloresAnteriores: ", coloresAnteriores)
    #colors=[(204.,204.,204.),(204.,204.,204.),(204.,204.,204.),(204.,204.,204.)]
    #colors=[(0.8,0.8,0.8),(0.8,0.8,0.8),(0.8,0.8,0.8),(0.8,0.8,0.8)]
    num_faces = len(obj.Shape.Faces)


    #for i, t in enumerate(coloresAnteriores):
    #    print("entro al for")
    #    print("len(t): ", len(t))
    #    if (len(t) == num_faces and len(coloresAnteriores)==1):

#            print(f"Tuple at index {i} has less than 3 elements, por lo tanto es un objeto que entra por primera vez: {t}")
#            # Perform any other action you need here
            # For example, you could replace the tuple with a default value
            #tuples_list[i] = (0.8, 0.8, 0.8)
            #print(f"Replaced tuple at index {i} with: {tuples_list[i]}")
#            coloresAnteriores=[(0.8,0.8,0.8)]*num_faces
#            print("entro al print raro")
 #           break
            
    if (len(coloresAnteriores) == num_faces): #Tantas tuplas como caras. Es modificado, a menos de que tenga una sola cara donde no es modificado
        if(num_faces==1 and len(coloresAnteriores[0])==1):#Siempre el no modificado tira una sola tupla. Si es una sola cara y la primera tupla tiene un solo elemento
            #print("No es modificado")
            coloresAnteriores=[(0.8,0.8,0.8)]*num_faces
        elif (num_faces==1 and len(coloresAnteriores[0])==3):
            #print("Si es modificado")
            pass
    elif (len(coloresAnteriores) != num_faces):
        #print("No es modificado")
        coloresAnteriores=[(0.8,0.8,0.8)]*num_faces


    

#or len(coloresAnteriores[0])!=3):#ejemplo 1 tupla 4 caras. Lo unico que puede pasar es 1 tupla si hay 1 cara. Seria 1 tupla con 1 solo elemeto en la tupla
    #    print("NO HA SIDO MODIFICADO")#Original siempre hace una sola tupla osea: len(coloresAnteriores) es 1
    #Cuando modificado va a tener tantas tuplas como caras
    #colors=[(1.,1.,0.),(1.,0.,1.),(1.,1.,0.),(1.,1.,0.)]
    # Set the color of the specific face
    #colors[face_index-1] = color
    coloresAnteriores[face_index-1] = color
    #view_obj.DiffuseColor = colors
    view_obj.DiffuseColor = coloresAnteriores
    
    # Recompute the document to apply changes
    App.ActiveDocument.recompute()


if False:
    func_changeColors("Cilindrito1", 2, "bocaGrande")
    func_changeColors("Cilindrito1", 3, "bocaGrande")
    func_changeColors("Cilindrito2", 2, "bocaGrande")
    func_changeColors("Cilindrito2", 3, "bocaGrande")
    func_changeColors("Cilindrito3", 2, "bocaGrande")
    func_changeColors("Cilindrito3", 3, "bocaGrande")
    func_changeColors("Cilindrito4", 2, "bocaGrande")
    func_changeColors("Cilindrito4", 3, "bocaGrande")

    func_changeColors("Clone1", 1, "bocaGrande")
    func_changeColors("Clone1", 5, "bocaPequeña")
    func_changeColors("Clone2", 1, "bocaGrande")
    func_changeColors("Clone2", 5, "bocaPequeña")
    func_changeColors("Clone3", 1, "bocaGrande")
    func_changeColors("Clone3", 5, "bocaPequeña")
    func_changeColors("Clone4", 1, "bocaGrande")
    func_changeColors("Clone4", 5, "bocaPequeña")
    func_changeColors("Clone5", 1, "bocaGrande")
    func_changeColors("Clone5", 5, "bocaPequeña")
    func_changeColors("Clone6", 1, "bocaGrande")
    func_changeColors("Clone6", 5, "bocaPequeña")

func_changeColors("TShape1", 2, "bocaGrande")
func_changeColors("TShape1", 5, "bocaGrande")
func_changeColors("TShape1", 3, "bocaPequeña")

func_changeColors("TShape2", 2, "bocaGrande")
func_changeColors("TShape2", 5, "bocaGrande")
func_changeColors("TShape2", 3, "bocaPequeña")

func_changeColors("CilindroGrande1", 1, "bocaPequeña")
func_changeColors("CilindroGrande2", 1, "bocaPequeña")
func_changeColors("CilindroGrande3", 1, "bocaPequeña")
func_changeColors("CilindroGrande4", 1, "bocaPequeña")


func_changeColors("Cilindrito1", 1, "bocaGrande")
func_changeColors("Cilindrito2", 1, "bocaGrande")
func_changeColors("Cilindrito3", 1, "bocaGrande")
func_changeColors("Cilindrito4", 1, "bocaGrande")

func_changeColors("CilindritoAserruchado1", 1, "bocaPequeña")
func_changeColors("CilindritoAserruchado2", 1, "bocaPequeña")
func_changeColors("CilindritoAserruchado3", 1, "bocaPequeña")
func_changeColors("CilindritoAserruchado4", 1, "bocaPequeña")


func_changeColors("Clone1", 4, "bocaGrande")
func_changeColors("Clone1", 2, "bocaPequeña")
func_changeColors("Clone2", 4, "bocaGrande")
func_changeColors("Clone2", 2, "bocaPequeña")
func_changeColors("Clone3", 4, "bocaGrande")
func_changeColors("Clone3", 2, "bocaPequeña")
func_changeColors("Clone4", 4, "bocaGrande")
func_changeColors("Clone4", 2, "bocaPequeña")
func_changeColors("Clone5", 4, "bocaGrande")
func_changeColors("Clone5", 2, "bocaPequeña")
func_changeColors("Clone6", 4, "bocaGrande")
func_changeColors("Clone6", 2, "bocaPequeña")


obj = doc.getObject("CilindritoAserruchado2")
obj.Visibility = not obj.Visibility
obj = doc.getObject("CilindritoAserruchado4")
obj.Visibility = not obj.Visibility
Gui.updateGui()

doc.recompute()
